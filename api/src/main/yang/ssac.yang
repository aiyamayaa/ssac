module ssac {
    yang-version 1;
    namespace "urn:opendaylight:params:xml:ns:yang:ssac";
    prefix "ssac";

    revision "2015-01-05" {
        description "Initial revision of ssac model";
    }
}
